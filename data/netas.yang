module netas {
    namespace "urn:coding_challenge";
    prefix cc;

    container device {
        leaf manufacturer {
            type string;
        }
        leaf manuuid {
            type string;
        }
        leaf model {
            type string;
        }
        leaf serial {
            type string;
        }
        leaf user_types {
            type string;
        }
    }
}
